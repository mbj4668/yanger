module ENG-21900-2 {
  yang-version 1.1;
  namespace "http://tail-f.com/eng-21900-2";
  prefix eng-2;

  import ENG-21900-1 {
    prefix eng-1;
  }

  feature enabled-feature;
  feature disabled-feature;

  typedef typedef-leafref {
    type leafref {
      require-instance false;
      path "/the-container/the-list/the-leaf";
    }
    description
      "If typedef has bad-path, we should NOT report error.";
  }

  leaf bad-path-no-prefix {
    type leafref {
      require-instance false;
      path "/the-container/the-list/the-leaf";
    }
    description
      "If a node has bad-path, make sure we report error.";
  }

  leaf bad-path-has-prefix {
    type leafref {
      require-instance false;
      path "/eng-2:the-container/eng-2:the-list/eng-2:the-leaf";
    }
    description
      "If a node has bad-path, make sure we report error.";
  }

  leaf uses-typedef-1 {
    type typedef-leafref;
    description
      "If a node uses typedef has bad-path, we should report error.";
  }

  leaf uses-typedef-2 {
    type typedef-leafref;
    description
      "If many node uses one typedef has bad-path,
       make sure we only report the error once.";
  }

  leaf uses-imported-typedef-no-prefix {
    type eng-1:typedef-leafref-no-prefix;
  }

  leaf uses-imported-typedef-has-prefix {
    type eng-1:typedef-leafref-has-prefix;
  }

  container the-container {
    list the-list {
      if-feature "disabled-feature";
      key name;
      leaf name {
        type string;
      }
      leaf the-leaf {
        type string;
      }
    }
  }
}
