module a-dev {
  yang-version 1.1;
  namespace "urn:example:a-dev";
  prefix adev;

  import a {
    prefix a;
  }

  deviation "/a:test/a:foo" {
    deviate delete {
      mandatory true;
    }
  }
}
