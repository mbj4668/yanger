module aug-dev-mand {
  namespace urn:aug-dev-mand;
  prefix aug-dev-mand;

  import test-a {
    prefix t-a;
  }

  augment /t-a:it {
    container item {
      leaf name { // LINE: YANG_ERR_MANDATORY_NODE_IN_AUGMENT
        type string;
      }
    }
    container p {
      presence "";
      leaf name {
        type string;
        mandatory false;
      }
    }
    list l { // LINE: YANG_ERR_MANDATORY_NODE_IN_AUGMENT
      key k;
      leaf k {
        type string;
      }
    }
  }

  // => mandatory augment
  deviation /t-a:it/item/name {
    deviate add {
      mandatory true;
    }
  }
  // no mandatory augment since p is presence container
  deviation /t-a:it/p/name {
    deviate replace {
      mandatory true;
    }
  }
  // => mandatory augment
  deviation /t-a:it/l {
    deviate add {
      min-elements 1;
    }
  }
}
