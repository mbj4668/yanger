module dev {
  namespace "urn:dummy";
  prefix dummy;

  import simple { prefix s1; }

  deviation "/s1:servers/s1:server/s1:name" {
    deviate add {
      must "current() < no-existing";
    }
  }

  deviation "/s1:servers/s1:server/s1:port" {
    deviate delete {
      must ". < 1024";
    }
  }
}
