module a {
  namespace urn:a;
  prefix a;

  grouping EXTERNAL-OUT {
    leaf external-out {
      type boolean;
    }
  }

  grouping AREA-TABLE {

    grouping AREA-CONTENT {
      uses EXTERNAL-OUT;
    }

    uses AREA-CONTENT;
  }

  container ospf {
    uses AREA-TABLE;
  }

}
