module test {
  yang-version 1.1;
  namespace "http://acme/test";
  prefix t;
  include subtarget;
  include subtest;
  
  leaf basename {
    if-feature name;
    type string;
    default "testname";
  }
}
