module config {
  yang-version 1.1;
  namespace "http://ekinops.com/otns/config";
  prefix otnsc;

  import tailf-common {
    prefix tailf;
  }

  list interface {
    description "OTN Interface list";
    tailf:info "OTN Interface list";
    key 'name';
    leaf name {
      description "(otu4|otu2|otu2e|odu4|odu2|odu2e|odu1|odu0|oduflex|e1glan|e10glan|e10glanrt|e10gwan|e100glan|fc8g|fc10g|stm64|ochgroup|och):\\d+/\\d+/\\d+/\\d+(\\.\\d+){0,}";
      tailf:info "(otu4|otu2|otu2e|odu4|odu2|odu2e|odu1|odu0|oduflex|e1glan|e10glan|e10glanrt|e10gwan|e100glan|fc8g|fc10g|stm64|ochgroup|och):\\d+/\\d+/\\d+/\\d+(\\.\\d+){0,}";
      type string {
        pattern "(otu4|otu2|otu2e|odu4|odu2|odu2e|odu1|odu0|oduflex|e1glan|e10glan|e10glanrt|e10gwan|e100glan|fc8g|fc10g|stm64|ochgroup|och):\\d+/\\d+/\\d+/\\d+(\\.\\d+){0,}";
      }
    }
  }
} // config module
