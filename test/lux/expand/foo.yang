module foo {
  namespace "urn:foo";
  prefix foo;

  typedef mytype {
    type string;
  }

  container foo {
    list bar {
      key k;
      leaf k {
        type string;
      }
      uses hello;
      uses goodbye;
      leaf bazinga {
        type int64;
      }
    }
  }

  grouping hello {
    leaf hello-1 {
      type mytype;
    }
    typedef type2 {
      type string;
    }
    leaf hello-2 {
      type type2;
    }
  }
  grouping goodbye {
    typedef type2 {
      type uint32;
    }
    leaf hello-3 {
      type type2;
    }
  }
}
