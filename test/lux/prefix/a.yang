module a {
  namespace urn:a;
  prefix a;

  import b {
    prefix b;
  }
  import c {
    prefix c;
  }

  container x {
//    must "foo()";
  }

  uses b:b;

  leaf g {
    type string;
    must "/c:q";
  }

}
