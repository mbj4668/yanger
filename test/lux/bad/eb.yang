module eb {
  namespace urn:eb;
  prefix eb;

  typedef e1 {
    type enumeration {
      enum a;
      enum b {
        value 0; // LINE: YANG_ERR_DUPLICATE_ENUM_VALUE
      }
      enum c;
      enum d {
        value 2147483647;
      }
      enum a; // LINE: YANG_ERR_DUPLICATE_ENUM_NAME
      enum e; // LINE: YANG_ERR_ENUM_VALUE
      enum f {
        value -2147483649; // LINE: YANG_ERR_ENUM_VALUE
      }
    }
  }
  typedef e2 {
    type e1 {
      enum a; // LINE: YANG_ERR_BAD_RESTRICTION
    }
  }

  typedef b1 {
    type bits {
      bit a;
      bit b {
        position 0; // LINE: YANG_ERR_DUPLICATE_BIT_POSITION
      }
      bit c;
      bit d {
        position 4294967296; // LINE: YANG_ERR_BIT_POSITION
      }
      bit a; // LINE: YANG_ERR_DUPLICATE_BIT_NAME
    }
  }
  typedef b2 {
    type b1 {
      bit a; // LINE: YANG_ERR_BAD_RESTRICTION
    }
  }
}
