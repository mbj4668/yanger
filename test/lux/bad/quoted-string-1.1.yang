module quoted-string-1.1 {
  yang-version 1.1;
  namespace urn:example:qs;
  prefix qs;

  description
    "Newline is ok.\nAnd tab\t, and a slash\\, and a
     double quote \".";

  container x {
    description
      "But nothing else! \'."; // LINE: YANG_ERR_PARSE_ILLEGAL_ESCAPE
  }
}
