submodule b-sub2 {

  belongs-to b {
    prefix b;
  }

  import a {
    prefix a;
  }

  augment "/a:vlan" {
    leaf add {
      type int32;
    }
  }

  leaf ports {
    type leafref {
      path "/a:vlan/add";
    }
  }
}
