module a-aug-dev {
  namespace urn:a-aug-dev;
  prefix aad;

  import a {
    prefix a;
  }
  import a-aug {
    prefix aa;
  }
  import b {
    prefix b;
  }

  deviation /a:a/aa:a {
    deviate add {
      must "k > /b:b";
    }
  }
}
