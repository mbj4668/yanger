module a {
  namespace urn:a;
  prefix a;

  identity foo {
    status deprecated;
  }
  identity bar {
    status obsolete;
  }

  leaf foo {
    status deprecated;
    type string;
  }
  leaf bar {
    status obsolete;
    type string;
  }
}
