module a {
  namespace urn:a;
  prefix a;

  container x {
    config false;
    list foo {
      leaf bar {
        type int32;
      }
      choice a-pretty-long-name {
        case another-long-name {
          leaf baz {
            type int32;
          }
        }
      }
    }
  }
}
