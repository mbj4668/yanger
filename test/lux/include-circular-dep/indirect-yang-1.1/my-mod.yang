module my-mod {

  yang-version "1.1";

  namespace "my:nice:conf";

  prefix "mod";

  include my-sub1;
  include my-sub2;
  include my-sub3;

  container configure {
    leaf hello {
      type string;
    }
  }
}
