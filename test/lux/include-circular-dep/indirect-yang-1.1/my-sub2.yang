submodule my-sub2 {

  yang-version "1.1";

  belongs-to my-mod { prefix "mod"; }

  include my-sub1;

  grouping sub2-grouping {
    container b {
      leaf y {
        type string;
      }
    }
  }
}
