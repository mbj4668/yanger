submodule my-sub3 {

  yang-version "1.1";

  belongs-to my-mod { prefix "mod"; }

  include my-sub2;

  grouping sub3-grouping {
    container c {
      leaf z {
        type string;
      }
    }
  }
}
