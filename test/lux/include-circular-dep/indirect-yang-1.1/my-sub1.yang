submodule my-sub1 {

  yang-version "1.1";

  belongs-to my-mod { prefix "mod"; }

  include my-sub3;

  grouping sub1-grouping {
    container a {
      leaf x {
        type boolean;
      }
    }
  }
}
