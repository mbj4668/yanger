module a {
  yang-version 1.1;
  namespace urn:a;
  prefix a;

  import ietf-yang-structure-ext {
    prefix sx;
  }

  sx:structure address-book {
    list address {
      leaf name {
        type string;
      }
      leaf address {
        type string;
      }
    }
  }
}
